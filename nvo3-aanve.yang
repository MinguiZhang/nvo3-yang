module nvo3-aanve {
  namespace "http://www.huawei.com/netconf/nvo3";
  prefix nvo3-aanve;
  import ietf-inet-types {
         prefix "inet";
  }
  import ietf-interfaces {
    prefix if;
  }
  import ietf-yang-types {
    prefix yang;
  }
 
  organization "IETF NVO3 Working Group";
  contact "zhangmingui@huawei.com";
  description
    "The module for nvo3 active-active edge configuration";
  
  revision 2014-09-11 {
    description
      "Initial revision.";
  }

  typedef NVE-ID {
    type union {
      type inet:ipv4-address;
      type inet:ipv6-address;
    }
    description
      "Defines addresses of different nves, IPv4 or IPv6";
  }

  typedef END-DEVICE-ID{
    type string;
    description
      "The identification of the end device that is 
      multi-attached to those NVEs given by the 'nve-list'; If the
      end device is an MC-LAG, it's an 8-octet value ID 
      according to Section 5.3.2 in 802.1ax-2008";
  } 

  typedef VNI {
     type uint32{
      range "1 .. 16777215";
    }
    description
      "Virtual Network Instance (VNI)";
   }

  typedef TS-ADDRESS{
    type union{
      type yang:mac-address;
      type inet:ipv4-address;
      type inet:ipv6-address;
    }
    description
      "The address of the Tenant System";
  }

  list active-active-nve-groups{
    key "end-id";
    leaf end-id{
      type END-DEVICE-ID;
      description
        "The identification of the end device that is 
         multi-attached to the NVEs given in the 'nve-list'.";
    }
    
    container multi-attached-info{
      list nve-list{
        key "nve-id";
        leaf nve-id{
          type NVE-ID;
        }
        description
          "Any NVE can deliver traffic of any VNI in the 'vni-list' 
          in this container";      
        
        leaf priority {
           type enumeration {
             enum primary {
               value "1";
               description
                 "Primary egress NVE.";
             }
             enum backup {
               value "2";
               description
                 "Backup egress NVE.";
             }
           }
           description
             "Simple priority for distinguishing between primary 
             and backup egress NVEs in an AANVE for BUM packets.

             Backup egress NVEs MUST NOT egress a BUM packet.";
        }

        leaf-list vap-list{
          type if:interface-ref;
          description
            "This nve uses these interfaces to attach the end device 
            link identified by the 'end-id'. These interfaces MUST 
            NOT egress any packet whose source NVE is listed in 
            the 'nve-list'";//split horizon
        }
      }

      leaf-list vni {
        type VNI;
        description
          "A VNI enabled for the end device identified by the 
          'end-id'";
      }
      
      leaf-list attached-ts-addresses{
        type TS-ADDRESS;
        description
          "The list of the Tenant System Addresses that are 
          connected to the end device identified by the 'end-id'. For
          any address in this list, the remote nve can sent traffic 
          towards it within the 'vni' via any nve given in the 
          nve-list'";
      }    
    }
  }     
}
